;;; 手动标注调整工具 - AutoCAD 2022+ AutoLISP
;;; 命令：BZYD
;;; 核心接口：(bzym:move <LEADER ename-or-handle> <WCS displacement>)
;;; 返回：("OK" handle) / ("UNCHANGED" handle) / ("ERROR" code message)

(defun bzym:_dxf (code data)
  (cdr (assoc code data))
)

(defun bzym:_default (value fallback)
  (if value value fallback)
)

(defun bzym:_all (code data / out item)
  (setq out nil)
  (foreach item data
    (if (= (car item) code)
      (setq out (cons (cdr item) out))
    )
  )
  (reverse out)
)

(defun bzym:_without (code data / out item)
  (setq out nil)
  (foreach item data
    (if (/= (car item) code)
      (setq out (cons item out))
    )
  )
  (reverse out)
)

(defun bzym:_replace-points (code data points / out index item)
  (setq out nil index 0)
  (foreach item data
    (if (= (car item) code)
      (progn
        (setq out (cons (cons code (nth index points)) out))
        (setq index (1+ index))
      )
      (setq out (cons item out))
    )
  )
  (reverse out)
)

(defun bzym:_set-code-before (code value before-code data / out found item)
  (setq out nil found nil)
  (foreach item data
    (if (= (car item) code)
      (progn
        (setq out (cons (cons code value) out)
              found T)
      )
      (progn
        (if (and (not found) (null (assoc code data)) (= (car item) before-code))
          (setq out (cons (cons code value) out)
                found T)
        )
        (setq out (cons item out))
      )
    )
  )
  (if found
    (reverse out)
    (append (reverse out) (list (cons code value)))
  )
)

(defun bzym:_flip-attachment (value)
  (if (numberp value)
    (cond
      ((= value 1) 3)
      ((= value 2) 2)
      ((= value 3) 1)
      ((= value 4) 6)
      ((= value 5) 5)
      ((= value 6) 4)
      ((= value 7) 9)
      ((= value 8) 8)
      ((= value 9) 7)
      (T nil)
    )
    nil
  )
)

(defun bzym:_p3 (p)
  (cond
    ((and (listp p) (= (length p) 3)
          (numberp (car p)) (numberp (cadr p)) (numberp (caddr p))) p)
    ((and (listp p) (= (length p) 2)
          (numberp (car p)) (numberp (cadr p)))
     (list (car p) (cadr p) 0.0))
    (T nil)
  )
)

(defun bzym:_finite-number-p (x)
  (and (numberp x) (= x x) (< (abs x) 1.0e99))
)

(defun bzym:_finite-point-p (p / q)
  (setq q (bzym:_p3 p))
  (and q
       (bzym:_finite-number-p (car q))
       (bzym:_finite-number-p (cadr q))
       (bzym:_finite-number-p (caddr q)))
)

(defun bzym:_v+ (a b)
  (mapcar '+ a b)
)

(defun bzym:_v- (a b)
  (mapcar '- a b)
)

(defun bzym:_dot (a b)
  (+ (* (car a) (car b))
     (* (cadr a) (cadr b))
     (* (caddr a) (caddr b)))
)

(defun bzym:_length (v)
  (sqrt (bzym:_dot v v))
)

(defun bzym:_unit (v / n)
  (if (bzym:_finite-point-p v)
    (progn
      (setq v (bzym:_p3 v)
            n (bzym:_length v))
      (if (> n 1.0e-14)
        (mapcar '(lambda (x) (/ x n)) v)
        nil
      )
    )
    nil
  )
)

(defun bzym:_reflect-u (vector u)
  (bzym:_v- vector
    (mapcar '(lambda (x) (* 2.0 x (bzym:_dot vector u))) u))
)

(defun bzym:_normal (data / n)
  (setq n (bzym:_p3 (bzym:_default (bzym:_dxf 210 data) '(0.0 0.0 1.0))))
  (if n (bzym:_unit n) nil)
)

(defun bzym:_maxabs (points / m p x)
  (setq m 0.0)
  (foreach p points
    (foreach x p
      (if (> (abs x) m) (setq m (abs x)))
    )
  )
  m
)

(defun bzym:_epsilon (points / extent p q)
  (setq extent 1.0)
  (if points
    (progn
      (setq p (car points))
      (foreach q (cdr points)
        (setq extent (max extent (bzym:_length (bzym:_v- q p))))
      )
      (setq extent (max extent (bzym:_length p)))
    )
  )
  (max 1.0e-8 (* 1.0e-9 extent) (* 1.0e-10 (bzym:_maxabs points)))
)

(defun bzym:_resolve (value)
  (cond
    ((and value (= (type value) 'ENAME)) value)
    ((and value (= (type value) 'STR)) (handent value))
    (T nil)
  )
)

(defun bzym:_entget (entity)
  (if entity (entget entity '("*")) nil)
)

(defun bzym:_owner (data / item in-reactors before-entity owner)
  ;; 330 inside {ACAD_REACTORS} is a reactor handle, not the entity owner.
  ;; The owner is the first 330 outside that group and before AcDbEntity.
  (setq in-reactors nil before-entity T owner nil)
  (foreach item data
    (cond
      ((and (= (car item) 102) (= (cdr item) "{ACAD_REACTORS"))
       (setq in-reactors T))
      ((and (= (car item) 102) (= (cdr item) "}") in-reactors)
       (setq in-reactors nil))
      ((and (= (car item) 100) (= (cdr item) "AcDbEntity"))
       (setq before-entity nil))
      ((and before-entity (not in-reactors) (= (car item) 330) (null owner))
       (setq owner (cdr item)))
    )
  )
  owner
)

(defun bzym:_locked-p (data / layer rec flags)
  (setq layer (bzym:_dxf 8 data)
        rec (if layer (tblsearch "LAYER" layer) nil)
        flags (if rec (bzym:_default (bzym:_dxf 70 rec) 0) 0))
  (and rec (/= 0 (logand flags 4)))
)

(defun bzym:_same-owner-p (a b)
  (and (bzym:_owner a)
       (bzym:_owner b)
       (equal (bzym:_owner a) (bzym:_owner b)))
)

(defun bzym:_shared-text-state (leader text owner / ss i en d ref found)
  (setq ss (ssget "_X" '((0 . "LEADER")))
        found nil)
  (if (null ss)
    (list "ERROR" "scan_failed" "无法扫描同空间LEADER，不能确认MTEXT是否被共用。")
    (progn
      (setq i 0)
      (while (and (< i (sslength ss)) (not found))
        (setq en (ssname ss i)
              d (bzym:_entget en)
              ref (bzym:_resolve (bzym:_dxf 340 d)))
        (if (and d
                 (not (eq en leader))
                 (equal (bzym:_owner d) owner)
                 ref
                 (eq ref text))
          (setq found T)
        )
        (setq i (1+ i))
      )
      (list "OK" found)
    )
  )
)

(defun bzym:_error-result (code message)
  (list "ERROR" code message)
)

(defun bzym:_inspect (entity / en ld ref td verts p0 p1 p2 norm tnorm eps owner shared)
  (setq en (bzym:_resolve entity))
  (if (null en)
    (bzym:_error-result "not_found" "找不到所选实体。")
    (progn
      (setq ld (bzym:_entget en))
      (cond
        ((null ld)
         (bzym:_error-result "not_readable" "无法读取LEADER实体。"))
        ((/= (bzym:_dxf 0 ld) "LEADER")
         (bzym:_error-result "unsupported_type" "请选择普通LEADER；不支持多重引线或其他对象。"))
        ((/= (bzym:_default (bzym:_dxf 76 ld) 0) 3)
         (bzym:_error-result "vertex_count" "仅支持恰有三个顶点的LEADER。"))
        ((and (bzym:_dxf 72 ld) (/= (bzym:_dxf 72 ld) 0))
         (bzym:_error-result "spline" "样条LEADER不支持。"))
        ((/= (length (bzym:_all 10 ld)) 3)
         (bzym:_error-result "vertex_count" "LEADER顶点数据与三顶点要求不符。"))
        ((/= (bzym:_default (bzym:_dxf 73 ld) 0) 0)
         (bzym:_error-result "no_annotation_flag" "LEADER未标记为文字注释引线。"))
        ((null (setq ref (bzym:_resolve (bzym:_dxf 340 ld))))
         (bzym:_error-result "no_annotation" "LEADER没有可读取的DXF 340关联对象。"))
        (T
         (setq td (bzym:_entget ref))
         (cond
           ((or (null td) (/= (bzym:_dxf 0 td) "MTEXT"))
            (bzym:_error-result "annotation_type" "DXF 340关联对象不是可读取的MTEXT。"))
           ((not (bzym:_same-owner-p ld td))
            (bzym:_error-result "space_mismatch" "LEADER与MTEXT不在同一模型/布局空间。"))
           ((or (bzym:_locked-p ld) (bzym:_locked-p td))
            (bzym:_error-result "locked_layer" "LEADER或MTEXT所在图层已锁定。"))
           ((/= (car (setq shared (bzym:_shared-text-state en ref (bzym:_owner ld)))) "OK")
            shared)
           ((cadr shared)
            (bzym:_error-result "shared_annotation" "同一空间内有多个LEADER共用此MTEXT，已拒绝移动。"))
           ((/= (length (bzym:_all 10 td)) 1)
            (bzym:_error-result "mtext_location" "MTEXT插入点数据不明确。"))
           (T
            (setq verts (mapcar 'bzym:_p3 (bzym:_all 10 ld))
                  p0 (car verts)
                  p1 (cadr verts)
                  p2 (caddr verts)
                  norm (bzym:_normal ld)
                  tnorm (bzym:_normal td))
            (cond
              ((or (not (bzym:_finite-point-p p0))
                   (not (bzym:_finite-point-p p1))
                   (not (bzym:_finite-point-p p2))
                   (not (bzym:_finite-point-p (bzym:_dxf 10 td))))
               (bzym:_error-result "invalid_coordinate" "LEADER或MTEXT包含无效坐标。"))
              ((or (null norm) (null tnorm))
               (bzym:_error-result "invalid_normal" "LEADER或MTEXT法向量无效。"))
              (T
               (setq eps (bzym:_epsilon (append verts (list (bzym:_p3 (bzym:_dxf 10 td))))))
               (cond
                 ((< (abs (bzym:_dot norm tnorm)) (- 1.0 1.0e-8))
                  (bzym:_error-result "normal_mismatch" "LEADER与MTEXT法向量不平行，无法安全保持文字方向。"))
                 ((or (<= (bzym:_length (bzym:_v- p1 p0)) eps)
                      (<= (bzym:_length (bzym:_v- p2 p1)) eps))
                  (bzym:_error-result "degenerate_leader" "LEADER斜段或横段长度为零，无法安全移动。"))
                 ((or (> (abs (bzym:_dot norm (bzym:_v- p1 p0))) eps)
                      (> (abs (bzym:_dot norm (bzym:_v- p2 p0))) eps)
                      (> (abs (bzym:_dot norm (bzym:_v- (bzym:_p3 (bzym:_dxf 10 td)) p0))) eps))
                  (bzym:_error-result "nonplanar" "LEADER顶点或MTEXT不在同一平面，已拒绝移动。"))
                 (T (list "OK" en ref ld td verts norm eps))
               )
              )
            )
           )
         )
        )
      )
    )
  )
)

(defun bzym:_inspect-safe (entity / inspected)
  (setq inspected (vl-catch-all-apply 'bzym:_inspect (list entity)))
  (if (vl-catch-all-error-p inspected)
    (bzym:_error-result "caught_exception" (vl-catch-all-error-message inspected))
    inspected
  )
)

(defun bzym:_points-near-p (a b eps / ok)
  (setq ok (= (length a) (length b)))
  (while (and ok a b)
    (if (> (bzym:_length (bzym:_v- (bzym:_p3 (car a)) (bzym:_p3 (car b)))) eps)
      (setq ok nil)
    )
    (setq a (cdr a) b (cdr b))
  )
  ok
)

(defun bzym:_restore-pair (leader text old-leader old-text eps / pass ld td ok)
  (setq ld (bzym:_entget leader)
        td (bzym:_entget text))
  (if (and ld td (equal ld old-leader eps) (equal td old-text eps))
    T
    (progn
      (setq pass 0 ok nil)
  (while (and (< pass 3) (not ok))
    (if (not (equal (bzym:_entget text) old-text eps))
      (vl-catch-all-apply 'entmod (list old-text))
    )
    (if (not (equal (bzym:_entget leader) old-leader eps))
      (vl-catch-all-apply 'entmod (list old-leader))
    )
    (vl-catch-all-apply 'entupd (list leader))
    (vl-catch-all-apply 'entupd (list text))
    (setq ld (bzym:_entget leader)
          td (bzym:_entget text)
          ok (and ld td
                  (equal ld old-leader eps)
                  (equal td old-text eps)))
    (setq pass (1+ pass))
  )
  ok
    )
  )
)

(defun bzym:_apply-pair (leader text old-leader old-text expected-leader expected-text target-verts target-text eps / write-result current-leader current-text moved status final-leader final-text result)
  (setq write-result (vl-catch-all-apply 'entmod (list expected-leader)))
  (if (or (vl-catch-all-error-p write-result) (null write-result))
    (if (bzym:_restore-pair leader text old-leader old-text eps)
      (bzym:_error-result "leader_write_failed" "LEADER写入失败；已核实原对象保持不变。")
      (bzym:_error-result "rollback_failed" "LEADER写入失败且自动恢复未能确认，请立即撤销本次操作。"))
    (progn
      (setq current-leader (bzym:_entget leader)
            current-text (bzym:_entget text))
      (cond
        ((or (null current-leader) (null current-text)
             (not (bzym:_points-near-p (bzym:_all 10 current-leader) target-verts eps))
             (not (equal (bzym:_without 10 current-leader)
                         (bzym:_without 10 expected-leader) eps)))
         (setq status "leader_readback_failed"))
        ((bzym:_points-near-p (bzym:_all 10 current-text) (list target-text) eps)
         (cond
           ((equal (bzym:_without 10 current-text)
                   (bzym:_without 10 expected-text) eps)
            (setq moved T))
           ((equal (bzym:_without 10 current-text)
                   (bzym:_without 10 old-text) eps)
            (setq write-result (vl-catch-all-apply 'entmod (list expected-text)))
            (if (or (vl-catch-all-error-p write-result) (null write-result))
              (setq status "mtext_write_failed")
              (setq moved T)))
           (T (setq status "association_side_effect")))
        )
        ((and (bzym:_points-near-p (bzym:_all 10 current-text) (bzym:_all 10 old-text) eps)
              (or (equal (bzym:_without 10 current-text)
                         (bzym:_without 10 old-text) eps)
                  (equal (bzym:_without 10 current-text)
                         (bzym:_without 10 expected-text) eps)))
         (setq write-result (vl-catch-all-apply 'entmod (list expected-text)))
         (if (or (vl-catch-all-error-p write-result) (null write-result))
           (setq status "mtext_write_failed")
           (setq moved T)))
        (T (setq status "association_side_effect"))
      )
      (if moved
        (progn
          (entupd leader)
          (entupd text)
          (setq final-leader (bzym:_entget leader)
                final-text (bzym:_entget text))
          (setq result
            (if (and final-leader final-text
                     (bzym:_points-near-p (bzym:_all 10 final-leader) target-verts eps)
                     (bzym:_points-near-p (bzym:_all 10 final-text) (list target-text) eps)
                     (equal (bzym:_without 10 final-leader) (bzym:_without 10 expected-leader) eps)
                     (equal (bzym:_without 10 final-text) (bzym:_without 10 expected-text) eps))
              (list "OK" (bzym:_dxf 5 old-leader))
              (setq status "readback_failed")))
        )
      )
      (if status
        (if (bzym:_restore-pair leader text old-leader old-text eps)
          (cond
            ((= status "leader_readback_failed")
             (bzym:_error-result status "LEADER写入后回读不符；已恢复原对象。"))
            ((= status "mtext_write_failed")
             (bzym:_error-result status "MTEXT写入失败；已恢复原对象。"))
            ((= status "association_side_effect")
             (bzym:_error-result status "LEADER修改引发了未预期的MTEXT位移；已恢复原对象。"))
            (T (bzym:_error-result status "移动后属性、关联或偏移核读不符；已恢复原对象。")))
          (bzym:_error-result "rollback_failed" "移动过程失败且自动恢复未能确认，请立即撤销本次操作。"))
        (if result result (bzym:_error-result "internal_error" "移动未完成。"))
      )
    )
  )
)

(defun bzym:_move-core (entity delta / inspected en text ld td verts norm eps delta3 anchor elbow endpt tail target-elbow target-end target-text normal-text text-dir unit-tail dot-angle angle-tol attachment flipped expected-ld expected-td target-verts offset213 hookflag hookdir applied)
  (cond
    ((not (bzym:_finite-point-p delta))
     (bzym:_error-result "invalid_delta" "位移必须是有限的WCS三维向量。"))
    (T
     (setq delta3 (bzym:_p3 delta)
           inspected (bzym:_inspect entity))
     (if (/= (car inspected) "OK")
       inspected
       (progn
         (setq en (nth 1 inspected)
               text (nth 2 inspected)
               ld (nth 3 inspected)
               td (nth 4 inspected)
               verts (nth 5 inspected)
               norm (nth 6 inspected)
               eps (nth 7 inspected))
         (cond
           ((> (abs (bzym:_dot norm delta3)) eps)
            (bzym:_error-result "off_plane_delta" "WCS位移不在LEADER平面内；请让当前UCS与图面方向一致后重试。"))
           ((<= (bzym:_length delta3) eps)
            (list "UNCHANGED" (bzym:_dxf 5 ld)))
           (T
            (setq anchor (car verts)
                  elbow (cadr verts)
                  endpt (caddr verts)
                  tail (bzym:_v- endpt elbow)
                  target-elbow (bzym:_v+ elbow delta3)
                  normal-text (bzym:_v+ (bzym:_p3 (bzym:_dxf 10 td)) delta3)
                  dot-angle (bzym:_dot (bzym:_v- anchor target-elbow) tail)
                  angle-tol (* 1.0e-9
                               (bzym:_length (bzym:_v- anchor target-elbow))
                               (bzym:_length tail))
                  flipped (> dot-angle angle-tol)
                  target-end (if flipped (bzym:_v- target-elbow tail) (bzym:_v+ endpt delta3))
                  target-text normal-text
                  expected-ld (bzym:_replace-points 10 ld
                    (list anchor target-elbow target-end))
                  expected-td (bzym:_replace-points 10 td (list normal-text)))
            (if (<= (bzym:_length (bzym:_v- anchor target-elbow)) eps)
              (bzym:_error-result "degenerate_target" "新折点与锚点重合，无法形成有效标注线。")
              (if flipped
                (progn
                  (setq text-dir (bzym:_unit (bzym:_p3 (bzym:_dxf 11 td)))
                        unit-tail (bzym:_unit tail)
                        attachment (bzym:_flip-attachment (bzym:_dxf 71 td)))
                  (cond
                    ((null text-dir)
                     (bzym:_error-result "missing_text_direction" "锐角换侧需要有效的MTEXT DXF 11文字方向；已拒绝移动。"))
                    ((> (abs (bzym:_dot norm text-dir)) 1.0e-8)
                     (bzym:_error-result "invalid_text_direction" "MTEXT DXF 11文字方向不在引线平面内；已拒绝锐角换侧。"))
                    ((or (null unit-tail)
                         (< (abs (bzym:_dot text-dir unit-tail)) (- 1.0 1.0e-8)))
                     (bzym:_error-result "tail_not_parallel" "锐角换侧要求LEADER尾段平行于MTEXT文字方向；已拒绝移动。"))
                    ((null attachment)
                     (bzym:_error-result "unsupported_attachment" "锐角换侧需要可识别的MTEXT附件点；已拒绝移动。"))
                    ((and (bzym:_dxf 213 ld)
                          (not (bzym:_finite-point-p (bzym:_dxf 213 ld))))
                     (bzym:_error-result "invalid_annotation_offset" "LEADER DXF 213偏移无效；已拒绝锐角换侧。"))
                    ((and (= (bzym:_default (bzym:_dxf 75 ld) 0) 1)
                          (not (member (bzym:_default (bzym:_dxf 74 ld) 0) '(0 1))))
                     (bzym:_error-result "invalid_hook_direction" "LEADER DXF 74钩线方向标志无效；已拒绝锐角换侧。"))
                    (T
                     (setq target-text
                            (bzym:_reflect-u (bzym:_v- normal-text target-elbow) text-dir)
                            target-text (bzym:_v+ target-elbow target-text)
                           expected-td (bzym:_replace-points 10 td (list target-text))
                           expected-td (bzym:_set-code-before 71 attachment 72 expected-td))
                     (if (and (bzym:_dxf 213 ld)
                              (> (bzym:_length (bzym:_p3 (bzym:_dxf 213 ld))) 1.0e-14))
                       (setq offset213 (bzym:_reflect-u (bzym:_p3 (bzym:_dxf 213 ld)) text-dir)
                             expected-ld (bzym:_set-code-before 213 offset213 212 expected-ld))
                     )
                     (setq hookflag (bzym:_default (bzym:_dxf 75 ld) 0)
                           hookdir (bzym:_default (bzym:_dxf 74 ld) 0))
                     (if (= hookflag 1)
                       (setq expected-ld
                         (bzym:_set-code-before 74 (if (= hookdir 0) 1 0) 75 expected-ld))
                     )
                     (setq target-verts (list anchor target-elbow target-end)
                           applied (bzym:_apply-pair en text ld td expected-ld expected-td target-verts target-text eps))
                     (if (= (car applied) "OK")
                       (append applied (list "FLIPPED"))
                       applied)
                    )
                  )
                )
                (progn
                  (setq target-verts (list anchor target-elbow target-end))
                  (bzym:_apply-pair en text ld td expected-ld expected-td target-verts target-text eps)
                )
              )
            )
           )
         )
       )
     )
    )
  )
)

(defun bzym:move (entity delta / inspected en text old-leader old-text eps caught restored)
  (setq inspected (bzym:_inspect-safe entity))
  (cond
    ((/= (car inspected) "OK") inspected)
    (T
     (setq en (nth 1 inspected)
           text (nth 2 inspected)
           old-leader (nth 3 inspected)
           old-text (nth 4 inspected)
           eps (nth 7 inspected)
           caught (vl-catch-all-apply 'bzym:_move-core (list entity delta)))
     (if (vl-catch-all-error-p caught)
       (progn
         (setq restored (vl-catch-all-apply 'bzym:_restore-pair (list en text old-leader old-text eps)))
         (if (and (not (vl-catch-all-error-p restored)) restored)
           (bzym:_error-result "caught_exception" (vl-catch-all-error-message caught))
           (bzym:_error-result "rollback_failed" "捕获到内部错误后无法确认对象已恢复，请立即撤销本次操作。"))
       )
       caught
     )
    )
  )
)

(defun c:BZYD (/ *error* old-error undo-open picked preselected rejected en inspected info verts elbow base-ucs target-ucs base-wcs target-wcs delta result)
  (setq old-error *error*
        undo-open nil)
  (setq *error*
    (lambda (msg)
      (if undo-open
        (progn
          (vl-catch-all-apply 'command (list "_.UNDO" "_End"))
          (setq undo-open nil)
        )
      )
      (setq *error* old-error)
      (if (and msg
               (not (wcmatch (strcase msg) "*CANCEL*,*QUIT*,*EXIT*")))
        (princ (strcat "\nBZYD中止：" msg))
      )
      (princ)
    )
  )
  (setq preselected (ssget "_I")
        rejected nil)
  (cond
    ((and preselected (> (sslength preselected) 1))
     (setq rejected T)
     (princ "\nBZYD：检测到多个预选对象；请只预选一条引线后重试。"))
    ((and preselected (= (sslength preselected) 1))
     (setq picked (list (ssname preselected 0) nil))
     (sssetfirst nil nil))
    (T
     (setq picked (entsel "\n选择一条三顶点普通LEADER：")))
  )
  (if picked
    (progn
      (setq en (car picked)
            inspected (bzym:_inspect-safe en))
      (if (/= (car inspected) "OK")
        (princ (strcat "\nBZYD：" (caddr inspected)))
        (progn
          (setq info inspected
                verts (nth 5 info)
                elbow (cadr verts)
                base-ucs (trans elbow 0 1))
          (initget "Basepoint")
          (setq target-ucs (getpoint base-ucs "\n指定新折点（基点为当前折点），或输入 [Basepoint(B)] 使用自定义基点："))
          (if (= (type target-ucs) 'STR)
            (progn
              (setq base-ucs (getpoint "\n指定自定义基点："))
              (if base-ucs
                (setq target-ucs (getpoint base-ucs "\n指定新位置："))
              )
            )
          )
          (if (and target-ucs (/= (type target-ucs) 'STR))
            (progn
              (setq base-wcs (trans base-ucs 1 0)
                    target-wcs (trans target-ucs 1 0)
                    delta (bzym:_v- target-wcs base-wcs))
              (if (<= (bzym:_length delta) (nth 7 info))
                (princ "\nBZYD：位移为零，未修改对象。")
                (progn
                  (command "_.UNDO" "_Begin")
                  (setq undo-open T
                        result (bzym:move en delta))
                  (command "_.UNDO" "_End")
                  (setq undo-open nil)
                  (cond
                    ((= (car result) "OK")
                     (if (and (caddr result) (equal (caddr result) "FLIPPED"))
                       (princ "\nBZYD：检测到锐角，已自动换到另一侧；锚点保持不动。")
                       (princ "\nBZYD：已移动文字与横段，锚点保持不动。")))
                    ((= (car result) "UNCHANGED")
                     (princ "\nBZYD：未发生变化。"))
                    (T
                     (princ (strcat "\nBZYD：" (caddr result))))
                  )
                )
              )
            )
            (princ "\nBZYD：已取消，未修改对象。")
          )
        )
      )
    )
    (if (not rejected)
      (princ "\nBZYD：未选择对象，未修改图形。")
    )
  )
  (setq *error* old-error)
  (princ)
)

(princ "\n手动标注调整工具已加载。输入 BZYD 开始。")
(princ)
